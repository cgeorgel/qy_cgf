InputRecord DEFINITIONS IMPLICIT TAGS	::=

BEGIN


------------------------------------------------------------------------------
--
--  GPRS RECORDS
--
------------------------------------------------------------------------------

GPRSRecord	::= CHOICE 
--
-- Record values 20, 22..27 are specific
-- Record values 76..77 are MBMS specific
-- Record values 78..79 are EPC specific 
{
--	sgsnPDPRecord			[20] sGSNPDPRecord,
--	sgsnMMRecord			[22] sGSNMMRecord,
--	sgsnSMORecord			[23] sGSNSMORecord,
--	sgsnSMTRecord			[24] sGSNSMTRecord,
--	sgsnLCTRecord			[25] SGSNLCTRecord,
--	sgsnLCORecord			[26] SGSNLCORecord,
--	sgsnLCNRecord			[27] SGSNLCNRecord,
--
--
--	sgsnMBMSRecord			[76] SGSNMBMSRecord,
--	ggsnMBMSRecord			[77] GGSNMBMSRecord,
	sGWRecord				[78] SGWRecord,
	pGWRecord				[79] PGWRecord
}

SGWRecord 	::= SET
{
	recordType					[0] RecordType,
	servedIMSI					[3] IMSI,
	s-GWAddress					[4] GSNAddress,
	chargingID					[5] ChargingID,
	servingNodeAddress			[6] SEQUENCE OF GSNAddress,
	accessPointNameNI			[7] AccessPointNameNI OPTIONAL,
	pdpPDNType					[8] PDPType OPTIONAL,
	servedPDPPDNAddress			[9] PDPAddress OPTIONAL,
	dynamicAddressFlag			[11] DynamicAddressFlag OPTIONAL,
	listOfTrafficVolumes		[12] SEQUENCE OF ChangeOfCharCondition OPTIONAL,
	recordOpeningTime			[13] TimeStamp,
	duration					[14] CallDuration,
	causeForRecClosing			[15] CauseForRecClosing,
	diagnostics					[16] Diagnostics OPTIONAL,
	recordSequenceNumber		[17] INTEGER OPTIONAL,
	nodeID						[18] NodeID OPTIONAL,
	recordExtensions			[19] ManagementExtensions OPTIONAL,
	localSequenceNumber			[20] LocalSequenceNumber OPTIONAL,
	apnSelectionMode			[21] APNSelectionMode OPTIONAL,
	servedMSISDN				[22] MSISDN OPTIONAL,
	chargingCharacteristics		[23] ChargingCharacteristics,
	chChSelectionMode			[24] ChChSelectionMode OPTIONAL,
	iMSsignalingContext			[25] NULL OPTIONAL,
	servingNodePLMNIdentifier	[27] PLMN-Id OPTIONAL,
	servedIMEISV				[29] IMEI OPTIONAL,
	rATType						[30] RATType OPTIONAL,
	mSTimeZone 					[31] MSTimeZone OPTIONAL,
	userLocationInformation		[32] OCTET STRING OPTIONAL,
	sGWChange					[34] SGWChange OPTIONAL,
	servingNodeType				[35] SEQUENCE OF ServingNodeType,
	p-GWAddressUsed				[36] GSNAddress OPTIONAL,
	p-GWPLMNIdentifier			[37] PLMN-Id OPTIONAL,
	startTime					[38] TimeStamp OPTIONAL,
	stopTime					[39] TimeStamp OPTIONAL,
	pDNConnectionID				[40] ChargingID OPTIONAL,
	servedPDPPDNAddressExt 		[41] PDPAddress OPTIONAL

}

PGWRecord 	::= SET
{
	recordType						[0] RecordType,
	servedIMSI						[3] IMSI,
	p-GWAddress						[4] GSNAddress,
	chargingID						[5] ChargingID,
	servingNodeAddress				[6] SEQUENCE OF GSNAddress,
	accessPointNameNI				[7] AccessPointNameNI OPTIONAL,
	pdpPDNType						[8] PDPType OPTIONAL,
	servedPDPPDNAddress				[9] PDPAddress OPTIONAL,
	dynamicAddressFlag				[11] DynamicAddressFlag OPTIONAL,
	recordOpeningTime				[13] TimeStamp,
	duration						[14] CallDuration,
	causeForRecClosing				[15] CauseForRecClosing,
	diagnostics						[16] Diagnostics OPTIONAL,
	recordSequenceNumber			[17] INTEGER OPTIONAL,
	nodeID							[18] NodeID OPTIONAL,
--	recordExtensions				[19] ManagementExtensions OPTIONAL,
	localSequenceNumber				[20] LocalSequenceNumber OPTIONAL,
	apnSelectionMode				[21] APNSelectionMode OPTIONAL,
	servedMSISDN					[22] MSISDN OPTIONAL,
	chargingCharacteristics			[23] ChargingCharacteristics,
	chChSelectionMode				[24] ChChSelectionMode OPTIONAL,
	iMSsignalingContext				[25] NULL OPTIONAL,
	externalChargingID				[26] OCTET STRING OPTIONAL,
	servinggNodePLMNIdentifier		[27] PLMN-Id OPTIONAL,
	pSFurnishChargingInformation	[28] PSFurnishChargingInformation OPTIONAL,
	servedIMEISV					[29] IMEI OPTIONAL,
	rATType							[30] RATType OPTIONAL,
	mSTimeZone 						[31] MSTimeZone OPTIONAL,
	userLocationInformation			[32] OCTET STRING OPTIONAL,
	cAMELChargingInformation		[33] OCTET STRING OPTIONAL,
	listOfServiceData				[34] SEQUENCE OF ChangeOfServiceCondition OPTIONAL,
	servingNodeType					[35] SEQUENCE OF ServingNodeType,
	servedMNNAI						[36] SubscriptionID OPTIONAL,
	p-GWPLMNIdentifier				[37] PLMN-Id OPTIONAL,
	startTime						[38] TimeStamp OPTIONAL,
	stopTime						[39] TimeStamp OPTIONAL,
	served3gpp2MEID					[40] OCTET STRING OPTIONAL,
	pDNConnectionID					[41] ChargingID OPTIONAL,
	servedPDPPDNAddressExt 			[43] PDPAddress OPTIONAL
}


------------------------------------------------------------------------------
--
--  Generic Data Types
--
------------------------------------------------------------------------------

CallDuration 			::= INTEGER
	--
	-- The call duration is counted in seconds. 
	-- For successful calls /sessions / PDP contexts, this is the chargeable duration.
	-- For call attempts this is the call holding time.
	-- 

RecordType 	::= INTEGER 
{ 
--
--	Record values 18..22 are GPRS specific.
--	The contents are defined in TS 32.251 [11]
--
	sGSNPDPRecord		(18),
	sGSNMMRecord		(20),
	sGSNSMORecord		(21),
	sGSNSMTRecord		(22),

	sGWRecord			(84),
	pGWRecord			(85)
}
PositionMethodFailure-Diagnostic ::= ENUMERATED {
	congestion  (0),
	insufficientResources  (1),
	insufficientMeasurementData  (2),
	inconsistentMeasurementData  (3),
	locationProcedureNotCompleted  (4),
	locationProcedureNotSupportedByTargetMS  (5),
	qoSNotAttainable  (6),
	positionMethodNotAvailableInNetwork	(7),
	positionMethodNotAvailableInLocationArea	(8) }
--	exception handling:
--	any unrecognized value shall be ignored

UnauthorizedLCSClient-Diagnostic ::= ENUMERATED {
	noAdditionalInformation (0),
	clientNotInMSPrivacyExceptionList (1),
	callToClientNotSetup (2),
	privacyOverrideNotApplicable (3),
	disallowedByLocalRegulatoryRequirements (4),
	unauthorizedPrivacyClass (5),
	unauthorizedCallSessionUnrelatedExternalClient (6),
	unauthorizedCallSessionRelatedExternalClient (7) }
--	exception handling:
--	any unrecognized value shall be ignored

Diagnostics						::= CHOICE
{
	gsm0408Cause				[0] INTEGER,
	-- See TS 24.008 [64]	
	gsm0902MapErrorValue		[1] INTEGER,
	-- Note: The value to be stored here corresponds to
	-- the local values defined in the MAP-Errors and 
	-- MAP-DialogueInformation modules, for full details
	-- see TS 29.002 [60].
	itu-tQ767Cause				[2] INTEGER,
	-- See ITU-T Q.767 [67]
--	networkSpecificCause		[3] ManagementExtension,
	-- To be defined by network operator	
--	manufacturerSpecificCause	[4] ManagementExtension,
	-- To be defined by manufacturer
	positionMethodFailureCause	[5] PositionMethodFailure-Diagnostic,
	-- see TS 29.002 [60]
	unauthorizedLCSClientCause	[6] UnauthorizedLCSClient-Diagnostic
	-- see TS 29.002 [60]
}

IPAddress	::= CHOICE
{
	iPBinaryAddress	 IPBinaryAddress,
	iPTextRepresentedAddress	 IPTextRepresentedAddress
}

IPBinaryAddress	::= CHOICE
{
	iPBinV4Address			[0] OCTET STRING (SIZE(4)),
	iPBinV6Address			[1] OCTET STRING (SIZE(16))
}

IPTextRepresentedAddress	::= CHOICE
{	
	--
	-- IP address in the familiar "dot" notation
	--
	iPTextV4Address			[2] IA5String (SIZE(7..15)),
	iPTextV6Address			[3] IA5String (SIZE(15..45))
}

LocalSequenceNumber ::= INTEGER (0..4294967295)
	--
	-- Sequence number of the record in this node
	-- 0.. 4294967295 is equivalent to 0..2**32-1, unsigned integer in four octets

maxAddressLength  INTEGER ::= 20

AddressString ::= OCTET STRING (SIZE (1..maxAddressLength))
	-- This type is used to represent a number for addressing
	-- purposes. It is composed of
	--	a)	one octet for nature of address, and numbering plan
	--		indicator.
	--	b)	digits of an address encoded as TBCD-String.

	-- a)	The first octet includes a one bit extension indicator, a
	--		3 bits nature of address indicator and a 4 bits numbering
	--		plan indicator, encoded as follows:

	-- bit 8: 1  (no extension)

	-- bits 765: nature of address indicator
	--	000  unknown
	--	001  international number
	--	010  national significant number
	--	011  network specific number
	--	100  subscriber number
	--	101  reserved
	--	110  abbreviated number
	--	111  reserved for extension

	-- bits 4321: numbering plan indicator
	--	0000  unknown
	--	0001  ISDN/Telephony Numbering Plan (Rec ITU-T E.164)
	--	0010  spare
	--	0011  data numbering plan (ITU-T Rec X.121)
	--	0100  telex numbering plan (ITU-T Rec F.69)
	--	0101  spare
	--	0110  land mobile numbering plan (ITU-T Rec E.212)
	--	0111  spare
	--	1000  national numbering plan
	--	1001  private numbering plan
	--	1111  reserved for extension

	--	all other values are reserved.

	-- b)	The following octets representing digits of an address
	--		encoded as a TBCD-STRING.

ISDN-AddressString ::= 
			AddressString (SIZE (1..20))
	-- This type is used to represent ISDN numbers.
	
	
MSISDN					::= ISDN-AddressString 
	-- 
	-- See TS 23.003 [68]
	--

MSTimeZone	::= OCTET STRING (SIZE (2))
	--
	-- 1.Octet: Time Zone and 2. Octet: Daylight saving time, see TS 29.060 [75]
	--

TimeStamp					::= OCTET STRING (SIZE(9))
	--
	-- The contents of this field are a compact form of the UTCTime format
	-- containing local time plus an offset to universal time. Binary coded
	-- decimal encoding is employed for the digits to reduce the storage and
	-- transmission overhead
	-- e.g. YYMMDDhhmmssShhmm
	-- where
	-- YY 	= 	Year 00 to 99		BCD encoded
	-- MM 	= 	Month 01 to 12 		BCD encoded
	-- DD	=	Day 01 to 31		BCD encoded
	-- hh	=	hour 00 to 23		BCD encoded
	-- mm	=	minute 00 to 59		BCD encoded
	-- ss	=	second 00 to 59		BCD encoded
	-- S	=	Sign 0 = "+", "-"	ASCII encoded
	-- hh	=	hour 00 to 23		BCD encoded
	-- mm	=	minute 00 to 59		BCD encoded
	--


------------------------------------------------------------------------------
--
--  PS DATA TYPES
--
------------------------------------------------------------------------------

AccessPointNameNI	::= IA5String (SIZE(1..63))
	--
	-- Network Identifier part of APN in  dot representation.
	-- For example, if the complete APN is 'apn1a.apn1b.apn1c.mnc022.mcc111.gprs'
	-- NI is 'apn1a.apn1b.apn1c' and is presented in this form in the CDR..
	--

AFChargingIdentifier ::= OCTET STRING
    --
    -- see AF-Charging-Identifier AVP as defined in TS 29.214[89]
    --

AFRecordInformation	::= SEQUENCE
{
	aFChargingIdentifier		[1] AFChargingIdentifier,
	flows						[2] Flows OPTIONAL
}

APNSelectionMode::= ENUMERATED
{
	--
	-- See Information Elements TS 29.060 [75], TS 29.274 [91] or TS 29.275 [92]
	--
	mSorNetworkProvidedSubscriptionVerified				(0),
	mSProvidedSubscriptionNotVerified					(1),
	networkProvidedSubscriptionNotVerified				(2)
}

CAMELAccessPointNameNI	::= AccessPointNameNI

CAMELAccessPointNameOI	::= AccessPointNameOI

ServiceKey ::= INTEGER (0..2147483647)

DefaultGPRS-Handling ::= ENUMERATED {
	continueTransaction (0),
	releaseTransaction 	(1)
}
-- exception handling:
-- reception of values in range 2-31 shall be treated as "continueTransaction"
-- reception of values greater than 31 shall be treated as "releaseTransaction"

LevelOfCAMELService  ::= BIT STRING { 
	basic      				(0),
	callDurationSupervision (1),
	onlineCharging    		(2),
	callPartyHandling   	(3)
}

CAMELInformationPDP	::= SET
{
	sCFAddress						[1] SCFAddress OPTIONAL,
	serviceKey						[2]	ServiceKey OPTIONAL,
	defaultTransactionHandling		[3]	DefaultGPRS-Handling OPTIONAL,
	cAMELAccessPointNameNI			[4] CAMELAccessPointNameNI OPTIONAL,
	cAMELAccessPointNameOI			[5] CAMELAccessPointNameOI OPTIONAL,
	numberOfDPEncountered			[6] NumberOfDPEncountered OPTIONAL,
	levelOfCAMELService				[7] LevelOfCAMELService OPTIONAL,
	freeFormatData					[8]	FreeFormatData OPTIONAL,
	fFDAppendIndicator				[9]	FFDAppendIndicator OPTIONAL
}

CauseForRecClosing	::= INTEGER
{
	--
	-- In PGW-CDR and SGW-CDR the value servingNodeChange is used for partial record
	-- generation due to Serving Node Address list Overflow
	-- In SGSN servingNodeChange indicates the SGSN change
	-- 	
	-- LCS related causes belong to the MAP error causes acc. TS 29.002 [60]
	--
	-- cause codes 0 to 15 are defined 'CauseForTerm' (cause for termination)
	--
	normalRelease					(0),
	abnormalRelease					(4),
	cAMELInitCallRelease			(5),
	volumeLimit						(16),
	timeLimit						(17),
	servingNodeChange				(18),
	maxChangeCond					(19),
	managementIntervention			(20),
	intraSGSNIntersystemChange		(21),
	rATChange						(22),
	mSTimeZoneChange				(23),
	sGSNPLMNIDChange 				(24),
	unauthorizedRequestingNetwork	(52),
	unauthorizedLCSClient			(53),
	positionMethodFailure			(54),
	unknownOrUnreachableLCSClient	(58),
	listofDownstreamNodeChange		(59)
}

ChangeCondition	::= ENUMERATED
{
	qoSChange								(0),
	tariffTime								(1),
	recordClosure							(2),
	cGI-SAICHange							(6), -- bearer modification. ��CGI-SAI Change��
	rAIChange								(7), -- bearer modification. ��RAI Change��
	dT-Establishment						(8),
	dT-Removal								(9),
	eCGIChange								(10), 	-- bearer modification. ��ECGI Change��
	tAIChange								(11), 	-- bearer modification. ��TAI Change��
	userLocationChange						(12)	-- bearer modification. ��User Location Change��
}

ChangeOfCharCondition	::= SEQUENCE
{
	--
	-- qosRequested and qosNegotiated are used in S-CDR only
	-- ePCQoSInformation used in SGW-CDR only
	--
	qosRequested				[1] QoSInformation OPTIONAL,
	qosNegotiated				[2] QoSInformation OPTIONAL,
	dataVolumeGPRSUplink		[3] DataVolumeGPRS OPTIONAL,
	dataVolumeGPRSDownlink		[4] DataVolumeGPRS OPTIONAL,
	changeCondition				[5] ChangeCondition,
	changeTime					[6] TimeStamp,
	userLocationInformation		[8] OCTET STRING OPTIONAL,
	ePCQoSInformation			[9] EPCQoSInformation OPTIONAL
}

ChangeOfServiceCondition	::= SEQUENCE
{
	--
	-- Used for Flow based Charging service data container
	--
	ratingGroup 					[1] RatingGroupId,
	chargingRuleBaseName			[2] ChargingRuleBaseName OPTIONAL,
	resultCode						[3] ResultCode OPTIONAL,
	localSequenceNumber				[4] LocalSequenceNumber OPTIONAL,
	timeOfFirstUsage				[5] TimeStamp OPTIONAL,
	timeOfLastUsage					[6] TimeStamp OPTIONAL,
	timeUsage 						[7] CallDuration OPTIONAL,
	serviceConditionChange			[8] ServiceConditionChange,
	qoSInformationNeg				[9] EPCQoSInformation OPTIONAL,
	servingNodeAddress 				[10] GSNAddress OPTIONAL,
	datavolumeFBCUplink				[12] DataVolumeGPRS OPTIONAL,
	datavolumeFBCDownlink			[13] DataVolumeGPRS OPTIONAL,
	timeOfReport					[14] TimeStamp,
	failureHandlingContinue			[16] FailureHandlingContinue OPTIONAL,
	serviceIdentifier				[17] ServiceIdentifier OPTIONAL,
	pSFurnishChargingInformation	[18] PSFurnishChargingInformation OPTIONAL,
	aFRecordInformation				[19] SEQUENCE OF AFRecordInformation OPTIONAL,
	userLocationInformation			[20] OCTET STRING OPTIONAL,
	eventBasedChargingInformation	[21] EventBasedChargingInformation OPTIONAL,
	timeQuotaMechanism				[22] TimeQuotaMechanism OPTIONAL,
	serviceSpecificInfo				[23] SEQUENCE OF ServiceSpecificInfo OPTIONAL
}

ChargingCharacteristics	::= OCTET STRING (SIZE(2))
    --
	--	Bit 0-3: Profile Index
	--	Bit 4-15: For Behavior
	--

ChargingID	::= INTEGER (0..4294967295)
	--
	-- Generated in P-GW, part of IP CAN bearer	 0..4294967295 is equivalent to 0..2**32-1
	--

ChargingRuleBaseName ::= IA5String (SIZE(1..16))
	-- 
	-- identifier for the group of charging rules
	-- see Charging-Rule-Base-Name AVP as desined in TS 29.212 [88]
	--

ChChSelectionMode		::= ENUMERATED
{
	servingNodeSupplied			(0),	-- For S-GW/P-GW
	subscriptionSpecific		(1),	-- For SGSN only
	aPNSpecific					(2),	-- For SGSN only
	homeDefault					(3),	-- For SGSN, S-GW and P-GW
	roamingDefault				(4),	-- For SGSN, S-GW and P-GW	
	visitingDefault				(5)		-- For SGSN, S-GW and P-GW
}

DataVolumeGPRS	::= INTEGER
	--
	-- The volume of data transferred in octets.
	--

DynamicAddressFlag	::=BOOLEAN

EPCQoSInformation	::= SEQUENCE
{
	--
	-- See TS 29.212 [88] for more information
	-- 
	qCI						[1] INTEGER,
	maxRequestedBandwithUL	[2] INTEGER OPTIONAL,
	maxRequestedBandwithDL	[3] INTEGER OPTIONAL,
	guaranteedBitrateUL		[4] INTEGER OPTIONAL,
	guaranteedBitrateDL		[5] INTEGER OPTIONAL,
	aRP						[6] INTEGER OPTIONAL
}

ETSIAddress	::= AddressString
	--
	-- First octet for nature of address, and numbering plan indicator (3 for X.121)
	-- Other octets TBCD
	-- See TS 29.002 [60]

	--

EventBasedChargingInformation  ::= SEQUENCE
{
	numberOfEvents		[1] INTEGER,
	eventTimeStamps  	[2] SEQUENCE OF TimeStamp OPTIONAL
}

FailureHandlingContinue  ::= BOOLEAN
	--
-- This parameter is included when the failure handling procedure has been executed and new 
-- containers are opened. This parameter shall be included in the first and subsequent 
-- containers opened after the failure handling execution.
	--

FFDAppendIndicator	::= BOOLEAN

Flows  ::= 	SEQUENCE
	--
	-- See Flows AVP as defined in TS 29.214 [89] 
	--
{
	mediaComponentNumber	[1] INTEGER,
	flowNumber  			[2] SEQUENCE OF INTEGER OPTIONAL
}

FreeFormatData	::=	OCTET STRING (SIZE(1..160))
	--
	-- Free formatted data as sent in the FurnishChargingInformationGPRS 
	-- see TS 29.078 [66]
	--

GSNAddress	::= IPAddress

NodeID	::= IA5String (SIZE(1..20))

NumberOfDPEncountered  ::= INTEGER

PDPAddress	::= CHOICE
{
	iPAddress			[0] IPAddress,
	eTSIAddress			[1] ETSIAddress
}

PDPType		::= OCTET STRING (SIZE(2))
	--
	-- OCTET 1: PDP Type Organization
	-- OCTET 2: PDP/PDN Type Number
	-- See TS 29.060 [75] for GTP, TS 29.274 [91] clause 8.14 for eGTP and TS 29.275 [92] for PMIP
	--

PLMN-Id		::= OCTET STRING (SIZE (3))
	--
	--	This is a 1:1 copy from the Routing Area Identity (RAI) IE specified in TS 29.060 [75]
	--  as follows:
	--	OCTET 1 of PLMN-Id = OCTET 2 of RAI  
	--	OCTET 2 of PLMN-Id = OCTET 3 of RAI  
	--	OCTET 3 of PLMN-Id = OCTET 4 of RAI  
	--


PSFurnishChargingInformation  ::= SEQUENCE
{
	pSFreeFormatData		[1] FreeFormatData,
	pSFFDAppendIndicator  	[2] FFDAppendIndicator OPTIONAL
}

QoSInformation	::= OCTET STRING (SIZE (4..255))
	--
	-- This  octet string 
	-- is a 1:1 copy of the contents (i.e. starting with octet 5) of the "Bearer Quality of 
	-- Service" information element specified in TS 29.274 [92].
	--

RatingGroupId ::= INTEGER
	-- 
	-- IP service flow identity (DCCA), range of 4 byte (0...4294967259)
	-- see Rating-Group AVP as used in TS 32.299 [40]
	--

RATType	::= INTEGER (0..255)
	--
	-- Ihis integer is 1:1 copy of the RAT type value as defined in TS 29.060 [75] for GTP, 
	-- TS 29.274 [91] for eGTP and TS 29.275 [92] for PMIP.
	--

ResultCode ::= INTEGER
	-- 
	-- charging protocol return value, range of 4 byte (0...4294967259)
	-- see Result-Code AVP as used in 3GPP 32.299 [40]
	--

ServiceConditionChange	::= BIT STRING 
{
	qoSChange 								 (0),	-- bearer modification
	sGSNChange 								 (1), 	-- bearer modification
	sGSNPLMNIDChange 						 (2), 	-- bearer modification
	tariffTimeSwitch 						 (3), 	-- tariff time change
	pDPContextRelease 						 (4), 	-- bearer release
	rATChange 								 (5),	-- bearer modification
	serviceIdledOut 						 (6),	-- IP flow idle out, DCCA QHT expiry
	reserved 								 (7),	-- old: QCTexpiry is no report event
	configurationChange 					 (8),	-- configuration change
	serviceStop 							 (9), 	-- IP flow termination
	dCCATimeThresholdReached 				(10),	-- DCCA quota reauthorization
	dCCAVolumeThresholdReached 				(11), 	-- DCCA quota reauthorization
	dCCAServiceSpecificUnitThresholdReached	(12), 	-- DCCA quota reauthorization
	dCCATimeExhausted 						(13), 	-- DCCA quota reauthorization
	dCCAVolumeExhausted 					(14), 	-- DCCA quota reauthorization
	dCCAValidityTimeout 					(15), 	-- DCCA quota validity time (QVT expiry)
	reserved1								(16),	-- reserved due to no use case, 
													-- old: return Requested is covered by (17),(18)
	dCCAReauthorisationRequest 				(17), 	-- DCCA quota reauthorization request by OCS
	dCCAContinueOngoingSession 				(18), 	-- DCCA failure handling (CCFH),
													-- continue IP flow
	dCCARetryAndTerminateOngoingSession		(19), 	-- DCCA failure handling (CCFH),
													-- terminate IP flow after DCCA retry
	dCCATerminateOngoingSession 			(20), 	-- DCCA failure handling,
													-- terminate IP flow
	cGI-SAIChange							(21), 	-- bearer modification.��CGI-SAI Change��
	rAIChange								(22), 	-- bearer modification.��RAI Change��
	dCCAServiceSpecificUnitExhausted		(23), 	-- DCCA quota reauthorization
	recordClosure							(24),	-- PGW-CDR closure
	timeLimit								(25),	-- intermediate recording
	volumeLimit								(26),	-- intermediate recording
	serviceSpecificUnitLimit				(27),	-- intermediate recording
	envelopeClosure 						(28),
	eCGIChange								(29), 	-- bearer modification. ��ECGI Change��
	tAIChange								(30), 	-- bearer modification. ��TAI Change��
	userLocationChange						(31)	-- bearer modification. ��User Location Change��
} 
--
-- Trigger and cause values for IP flow level recording are defined for support of independent
-- online and offline charging and also for tight interworking between online and offline charging.
-- Unused bits will always be zero.
-- Some of the values are non-exclusive (e.g. bearer modification reasons).
	--

SCFAddress	::= AddressString
	--
	-- See TS 29.002 [60]
	--

ServiceIdentifier	::= INTEGER (0..4294967295)
	--
	-- The service identifier is used to identify the service or the service component
	-- the service data flow relates to. See Service-Identifier AVP as defined 
	-- in TS 29.212 [88]
	--

ServingNodeType	::= ENUMERATED {
	sGSN		(0),
	pMIPSGW		(1),
	gTPSGW		(2),
	ePDG		(3),
	hSGW		(4),
	mME			(5)
}

SGWChange	::= BOOLEAN
	--
	-- present if first record after inter S-GW change
	--

TimeQuotaMechanism	::= SEQUENCE
{
	timeQuotaType					[1] TimeQuotaType,
	baseTimeInterval				[2] INTEGER
}

TimeQuotaType	::= ENUMERATED
{
	discreteTimePeriod			(0),
	continuousTimePeriod		(1)
}

IMSI ::= TBCD-STRING (SIZE (3..8))
	-- digits of MCC, MNC, MSIN are concatenated in this order.

IMEI ::= TBCD-STRING (SIZE (8))
        --      Refers to International Mobile Station Equipment Identity
        --      and Software Version Number (SVN) defined in TS GSM 03.03.
        --      If the SVN is not present the last octet shall contain the
        --      digit 0 and a filler.
        --      If present the SVN shall be included in the last octet.


TBCD-STRING ::= OCTET STRING
	-- This type (Telephony Binary Coded Decimal String) is used to
	-- represent several digits from 0 through 9, *, #, a, b, c, two
	-- digits per octet, each digit encoded 0000 to 1001 (0 to 9),
	-- 1010 (*), 1011 (#), 1100 (a), 1101 (b) or 1110 (c); 1111 used
	-- as filler when there is an odd number of digits.

	-- bits 8765 of octet n encoding digit 2n
	-- bits 4321 of octet n encoding digit 2(n-1) +1
ManagementExtension ::= SEQUENCE
{
	identifier      OBJECT IDENTIFIER,
	significance    [1] BOOLEAN DEFAULT FALSE,
	information     [2] OCTET STRING
}

ManagementExtensions    ::= SET OF ManagementExtension

SubscriptionID	::= SET
{
	subscriptionIDType	[0]	SubscriptionIDType,
	subscriptionIDData	[1]	UTF8String
}

SubscriptionIDType	::= ENUMERATED {
	endUserE164		(0),
	endUserIMSI		(1),
	endUserSIPURI   (2),
	endUserNAI		(3),
	endUserPrivate  (4)
}

AccessPointNameOI	::= IA5String (SIZE(1..37))
--
-- Operator Identifier part of APN in dot representation.
-- In the 'apn1a.apn1b.apn1c.mnc022.mcc111.gprs' example, the OI portion is 'mnc022.mcc111.gprs'
-- and is presented in this form in the CDR.
--
ServiceSpecificInfo  ::=  SEQUENCE
{
	serviceSpecificData		[0] GraphicString OPTIONAL, 
	serviceSpecificType		[1] INTEGER OPTIONAL
}

END
